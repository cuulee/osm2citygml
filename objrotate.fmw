FME workspace objrotate.fmw

Parameters:
- SourceDataset_OBJ = $(FME_MF_DIR)test.obj   # Source Wavefront OBJ File
- FEATURE_TYPES =
- DestDataset_OBJ =   # Destination Wavefront OBJ Folder

Readers:
- OBJ_1: OBJ from $(SourceDataset_OBJ)

Writers:
- OBJ_2: OBJ to $(DestDataset_OBJ)

test (reader OBJ_1)
    -> 3DRotator
3DRotator
    AXIS_CHOICE = X Axis
    ANGLE = 90
    ROTATED -> test (writer OBJ_2)
test (writer OBJ_2)
